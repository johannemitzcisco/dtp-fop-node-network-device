module dtp-fo-route-map { 

  namespace "http://www.cisco.com/dtp-fo-route-map";
  prefix dtpn-route-map;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping route-map-object {
    list route-map {
      key name;
      leaf name { type string; }
      list action {
        key action;
        leaf action {
          type ennumeration {
            enum "permit";
            enum "deny";
          }
        }
        
      }
    }
    leaf-list route-map-server-ip {
      type inet:ipv4-address;
    }
  }

  grouping route-map-fo {
    list route-map {
      key name;
      uses dtpn:function-object;
    }
  }

  augment /dtpn:dtp/dtpn:network/dtpn:topology/dtpn:function-objects {
    list route-map {
      max-elements 1;
      key "function-object-name";
      leaf function-object-name {
        type leafref {
          path "/dtpn:dtp/dtpn:function-object-definitions/dtpn:topology/route-map/name";
        }
      }
      uses route-map-object;
    }
  }

  augment /dtpn:dtp/dtpn:network/dtpn:topology/dtpn:node/dtpn:function-objects {
    list route-map {
      max-elements 1;
      key "function-object-name";
      leaf function-object-name {
        type leafref {
          path "/dtpn:dtp/dtpn:function-object-definitions/dtpn:node/route-map/name";
        }
      }
      uses route-map-object;
    }
  }

  augment /dtpn:dtp/dtpn:function-object-definitions/dtpn:topology {
    uses route-map-fo;
  }

  augment /dtpn:dtp/dtpn:function-object-definitions/dtpn:node {
    uses route-map-fo;
  }

}
