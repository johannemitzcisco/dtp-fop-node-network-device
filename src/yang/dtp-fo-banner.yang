module dtp-fo-banner { 

  namespace "http://www.cisco.com/dtp-fo-banner";
  prefix dtpn-banner;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping banner-object {
    leaf message-of-the-day {
      type string;
    }
  }

  grouping banner-fo {
    list banner {
      key name;
      uses dtpn:function-object;
    }
  }

  augment /dtpn:dtp/dtpn:network/dtpn:topology/dtpn:function-objects {
    list banner {
      max-elements 1;
      key "function-object-name";
      leaf function-object-name {
        type leafref {
          path "/dtpn:dtp/dtpn:function-object-definitions/dtpn:topology/banner/name";
        }
      }
      uses banner-object;
    }
  }

  augment /dtpn:dtp/dtpn:network/dtpn:topology/dtpn:node/dtpn:function-objects {
    list banner {
      max-elements 1;
      key "function-object-name";
      leaf function-object-name {
        type leafref {
          path "/dtpn:dtp/dtpn:function-object-definitions/dtpn:node/banner/name";
        }
      }
      uses banner-object;
    }
  }

  augment /dtpn:dtp/dtpn:function-object-definitions/dtpn:topology {
    uses banner-fo;
  }

  augment /dtpn:dtp/dtpn:function-object-definitions/dtpn:node {
    uses banner-fo;
  }

}
