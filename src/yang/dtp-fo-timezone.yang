module dtp-fo-timezone { 

  namespace "http:www.cisco.com/dtp-fo-timezone";
  prefix dtpn-timezone;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping timezone-object {
    leaf timezone {
      type string;
    }
    container offset {
      leaf hours {
        type int8 {
          range "-23..23";
        }
      }
      leaf minutes {
        type uint8 {
          range "0..59";
        }
      }
    }
  }

  grouping timezone-fo {
    list timezone {
      key name;
      uses dtpn:function-object;
    }
  }

  augment /dtpn:dtp/dtpn:network/dtpn:topology/dtpn:function-objects {
    list timezone {
      max-elements 1;
      key "function-object-name";
      leaf function-object-name {
        type leafref {
          path "/dtpn:dtp/dtpn:function-object-definitions/dtpn:topology/timezone/name";
        }
      }
      uses timezone-object;
    }
  }

  augment /dtpn:dtp/dtpn:network/dtpn:topology/dtpn:node/dtpn:function-objects {
    list timezone {
      max-elements 1;
      key "function-object-name";
      leaf function-object-name {
        type leafref {
          path "/dtpn:dtp/dtpn:function-object-definitions/dtpn:node/timezone/name";
        }
      }
      uses timezone-object;
    }
  }

  augment /dtpn:dtp/dtpn:function-object-definitions/dtpn:topology {
    uses timezone-fo;
  }

  augment /dtpn:dtp/dtpn:function-object-definitions/dtpn:node {
    uses timezone-fo;
  }

}
