module dtp-fo-tacacs { 

  namespace "http://www.cisco.com/dtp-fo-tacacs";
  prefix dtpn-tacacs;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping tacacs-object {
    list server {
      key ip-address;
      leaf ip-address {
        type inet:ipv4-address;
      }
      leaf port {
        type uint16;
      }
    }
    leaf port {
      type uint16;
    }
    leaf key {
      type string;
    }
  }

  grouping tacacs-fo {
    list tacacs {
      key name;
      uses dtpn:function-object;
    }
  }

  augment /dtpn:dtp/dtpn:network/dtpn:topology/dtpn:function-objects {
    list tacacs {
      max-elements 1;
      key "function-object-name";
      leaf function-object-name {
        type leafref {
          path "/dtpn:dtp/dtpn:function-object-definitions/dtpn:topology/tacacs/name";
        }
      }
      uses tacacs-object;
    }
  }

  augment /dtpn:dtp/dtpn:network/dtpn:topology/dtpn:node/dtpn:function-objects {
    list tacacs {
      max-elements 1;
      key "function-object-name";
      leaf function-object-name {
        type leafref {
          path "/dtpn:dtp/dtpn:function-object-definitions/dtpn:node/tacacs/name";
        }
      }
      uses tacacs-object;
    }
  }

  augment /dtpn:dtp/dtpn:function-object-definitions/dtpn:topology {
    uses tacacs-fo;
  }

  augment /dtpn:dtp/dtpn:function-object-definitions/dtpn:node {
    uses tacacs-fo;
  }

}
