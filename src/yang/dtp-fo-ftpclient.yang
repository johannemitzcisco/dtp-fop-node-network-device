module dtp-fo-ftpclient { 

  namespace "http://www.cisco.com/dtp-fo-ftpclient";
  prefix dtpn-ftpclient;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping ftpclient-object {
    leaf interface {
      type string;
    }
    leaf username {
      type string;
    }
    leaf password {
      type string;
    }
  }

  grouping ftpclient-fo {
    list ftpclient {
      key name;
      uses dtpn:function-object;
    }
  }

  augment /dtpn:dtp/dtpn:network/dtpn:topology/dtpn:function-objects {
    list ftpclient {
      max-elements 1;
      key "function-object-name";
      leaf function-object-name {
        type leafref {
          path "/dtpn:dtp/dtpn:function-object-definitions/dtpn:topology/ftpclient/name";
        }
      }
      uses ftpclient-object;
    }
  }

  augment /dtpn:dtp/dtpn:network/dtpn:topology/dtpn:node/dtpn:function-objects {
    list ftpclient {
      max-elements 1;
      key "function-object-name";
      leaf function-object-name {
        type leafref {
          path "/dtpn:dtp/dtpn:function-object-definitions/dtpn:node/ftpclient/name";
        }
      }
      uses ftpclient-object;
    }
  }

  augment /dtpn:dtp/dtpn:function-object-definitions/dtpn:topology {
    uses ftpclient-fo;
  }

  augment /dtpn:dtp/dtpn:function-object-definitions/dtpn:node {
    uses ftpclient-fo;
  }

}
