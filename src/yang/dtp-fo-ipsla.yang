module dtp-fo-ipsla { 

  namespace "http://www.cisco.com/dtp-fo-ipsla";
  prefix dtpn-ipsla;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping ipsla-object {
    container key-chain {
      leaf id {
        type uint8;
      }
      leaf name {
        type string;
      }
      leaf password {
        type string;
      }
    }
  }

  grouping ipsla-fo {
    list ipsla {
      key name;
      uses dtpn:function-object;
    }
  }

  augment /dtpn:dtp/dtpn:network/dtpn:topology/dtpn:function-objects {
    list ipsla {
      max-elements 1;
      key "function-object-name";
      leaf function-object-name {
        type leafref {
          path "/dtpn:dtp/dtpn:function-object-definitions/dtpn:topology/ipsla/name";
        }
      }
      uses ipsla-object;
    }
  }

  augment /dtpn:dtp/dtpn:network/dtpn:topology/dtpn:node/dtpn:function-objects {
    list ipsla {
      max-elements 1;
      key "function-object-name";
      leaf function-object-name {
        type leafref {
          path "/dtpn:dtp/dtpn:function-object-definitions/dtpn:node/ipsla/name";
        }
      }
      uses ipsla-object;
    }
  }

  augment /dtpn:dtp/dtpn:function-object-definitions/dtpn:topology {
    uses ipsla-fo;
  }

  augment /dtpn:dtp/dtpn:function-object-definitions/dtpn:node {
    uses ipsla-fo;
  }

}
