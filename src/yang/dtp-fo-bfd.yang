module dtp-fo-bfd { 

  namespace "http://www.cisco.com/dtp-fo-bfd";
  prefix dtpn-bfd;

  import dtp-network { prefix dtpn; }
  import ietf-inet-types { prefix inet; }
  import tailf-common { prefix tailf; }
  import tailf-ncs { prefix ncs; }

  description
    "This is an add on model to the dtp-network package/service";

  revision 2017-11-28 {
    description
      "Initial revision.";
  }

  grouping bfd-object {
  }

  grouping bfd-fo {
    list bfd {
      key name;
      uses dtpn:function-object;
    }
  }

  augment /dtpn:dtp/dtpn:network/dtpn:topology/dtpn:function-objects {
    list bfd {
      max-elements 1;
      key "function-object-name";
      leaf function-object-name {
        type leafref {
          path "/dtpn:dtp/dtpn:function-object-definitions/dtpn:topology/bfd/name";
        }
      }
      uses bfd-object;
    }
  }

  augment /dtpn:dtp/dtpn:network/dtpn:topology/dtpn:node/dtpn:function-objects {
    list bfd {
      max-elements 1;
      key "function-object-name";
      leaf function-object-name {
        type leafref {
          path "/dtpn:dtp/dtpn:function-object-definitions/dtpn:node/bfd/name";
        }
      }
      uses bfd-object;
    }
  }

  augment /dtpn:dtp/dtpn:function-object-definitions/dtpn:topology {
    uses bfd-fo;
  }

  augment /dtpn:dtp/dtpn:function-object-definitions/dtpn:node {
    uses bfd-fo;
  }

}
